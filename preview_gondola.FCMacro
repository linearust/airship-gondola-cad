"""Render the current assembly; terminal use returns after writing previews."""

import importlib
import os
import sys
from functools import partial
from pathlib import Path

from PySide import QtCore

# Reload the whole local package without closing or modifying open documents.
# Removing generated bytecode also handles same-second, same-size source edits;
# an unwritable cache aborts before rendering rather than using stale code.
_repo_root = Path(__file__).resolve().parent
for _cache in (_repo_root / "gondola").rglob("__pycache__/*.pyc"):
    _cache.unlink(missing_ok=True)
for _module_name in tuple(sys.modules):
    if _module_name == "gondola" or _module_name.startswith("gondola."):
        del sys.modules[_module_name]
sys.path[:] = [str(_repo_root), *[p for p in sys.path if p != str(_repo_root)]]
importlib.invalidate_caches()

from gondola.preview import render_previews  # noqa: E402

_close_after_preview = os.environ.get("GONDOLA_CLOSE_AFTER_PREVIEW") == "1"
QtCore.QTimer.singleShot(
    1200,
    partial(render_previews, close_after=_close_after_preview),
)
