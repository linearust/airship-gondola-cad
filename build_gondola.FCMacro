"""Build the current design from this folder in an installed FreeCAD GUI."""

import importlib
import sys
from pathlib import Path

import FreeCADGui as Gui

# FreeCAD keeps Python imports between macro runs. Discard the complete package
# and its generated bytecode so current files, including same-size edits made
# within one second, cannot be stamped onto geometry from cached source.
_repo_root = Path(__file__).resolve().parent
for _cache in (_repo_root / "gondola").rglob("__pycache__/*.pyc"):
    _cache.unlink(missing_ok=True)
for _module_name in tuple(sys.modules):
    if _module_name == "gondola" or _module_name.startswith("gondola."):
        del sys.modules[_module_name]
sys.path[:] = [str(_repo_root), *[p for p in sys.path if p != str(_repo_root)]]
importlib.invalidate_caches()

from gondola.assembly import build_assembly, style_assembly  # noqa: E402

doc = build_assembly()
style_assembly(doc)
Gui.activeDocument().activeView().viewAxonometric()
Gui.activeDocument().activeView().fitAll()
doc.save()
